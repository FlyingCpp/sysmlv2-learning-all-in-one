package LongLabels {
part '飞控接口控制器_ABCDEFGHIJKLMNOPQRSTUVWXYZ_长名称测试' { port '遥测数据接口_ABCDEFGHIJKLMNOPQRSTUVWXYZ'; } part other { port p; }
view target : StandardViewDefinitions::InterconnectionView { expose '飞控接口控制器_ABCDEFGHIJKLMNOPQRSTUVWXYZ_长名称测试'; expose other; }
}
