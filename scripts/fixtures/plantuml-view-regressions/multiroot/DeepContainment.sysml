package DeepContainment {
part a { part b { part c { part d { part e { part f { port p; } } } } } } part z { port p; }
view target : StandardViewDefinitions::InterconnectionView { expose a; expose z; }
}
