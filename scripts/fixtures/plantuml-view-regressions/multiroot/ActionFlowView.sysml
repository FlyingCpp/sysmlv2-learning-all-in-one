package MultiActionFlowView {
  item def Start; item def Request; item def Response;
  action def Root1 { action prepare; then action execute; then action complete; }
  action def Root2 { action prepare; then action execute; then action complete; }
  action def Root3 { action prepare; then action execute; then action complete; }
  action def Root4 { action prepare; then action execute; then action complete; }
  action def Root5 { action prepare; then action execute; then action complete; }
  action def Root6 { action prepare; then action execute; then action complete; }
  action def Root7 { action prepare; then action execute; then action complete; }
  action def Root8 { action prepare; then action execute; then action complete; }
  action def Root9 { action prepare; then action execute; then action complete; }
  action def Root10 { action prepare; then action execute; then action complete; }
  action def Root11 { action prepare; then action execute; then action complete; }
  action def Root12 { action prepare; then action execute; then action complete; }
  action def Root13 { action prepare; then action execute; then action complete; }
  action def Root14 { action prepare; then action execute; then action complete; }
  action def Root15 { action prepare; then action execute; then action complete; }
  action def Root16 { action prepare; then action execute; then action complete; }
  action def Root17 { action prepare; then action execute; then action complete; }
  action def Root18 { action prepare; then action execute; then action complete; }
  action def Root19 { action prepare; then action execute; then action complete; }
  action def Root20 { action prepare; then action execute; then action complete; }
  action def Root21 { action prepare; then action execute; then action complete; }
  action def Root22 { action prepare; then action execute; then action complete; }
  action def Root23 { action prepare; then action execute; then action complete; }
  action def Root24 { action prepare; then action execute; then action complete; }
  action def Root25 { action prepare; then action execute; then action complete; }
  action def Root26 { action prepare; then action execute; then action complete; }
  action def Root27 { action prepare; then action execute; then action complete; }
  action def Root28 { action prepare; then action execute; then action complete; }
  action def Root29 { action prepare; then action execute; then action complete; }
  action def Root30 { action prepare; then action execute; then action complete; }
  action def Root31 { action prepare; then action execute; then action complete; }
  action def Root32 { action prepare; then action execute; then action complete; }
  action def Root33 { action prepare; then action execute; then action complete; }
  view roots1 : StandardViewDefinitions::ActionFlowView {
      expose Root1;
    }
  view roots2 : StandardViewDefinitions::ActionFlowView {
      expose Root1;
      expose Root2;
    }
  view roots3 : StandardViewDefinitions::ActionFlowView {
      expose Root1;
      expose Root2;
      expose Root3;
    }
  view roots8 : StandardViewDefinitions::ActionFlowView {
      expose Root1;
      expose Root2;
      expose Root3;
      expose Root4;
      expose Root5;
      expose Root6;
      expose Root7;
      expose Root8;
    }
  view roots9 : StandardViewDefinitions::ActionFlowView {
      expose Root1;
      expose Root2;
      expose Root3;
      expose Root4;
      expose Root5;
      expose Root6;
      expose Root7;
      expose Root8;
      expose Root9;
    }
  view roots16 : StandardViewDefinitions::ActionFlowView {
      expose Root1;
      expose Root2;
      expose Root3;
      expose Root4;
      expose Root5;
      expose Root6;
      expose Root7;
      expose Root8;
      expose Root9;
      expose Root10;
      expose Root11;
      expose Root12;
      expose Root13;
      expose Root14;
      expose Root15;
      expose Root16;
    }
  view roots17 : StandardViewDefinitions::ActionFlowView {
      expose Root1;
      expose Root2;
      expose Root3;
      expose Root4;
      expose Root5;
      expose Root6;
      expose Root7;
      expose Root8;
      expose Root9;
      expose Root10;
      expose Root11;
      expose Root12;
      expose Root13;
      expose Root14;
      expose Root15;
      expose Root16;
      expose Root17;
    }
  view roots32 : StandardViewDefinitions::ActionFlowView {
      expose Root1;
      expose Root2;
      expose Root3;
      expose Root4;
      expose Root5;
      expose Root6;
      expose Root7;
      expose Root8;
      expose Root9;
      expose Root10;
      expose Root11;
      expose Root12;
      expose Root13;
      expose Root14;
      expose Root15;
      expose Root16;
      expose Root17;
      expose Root18;
      expose Root19;
      expose Root20;
      expose Root21;
      expose Root22;
      expose Root23;
      expose Root24;
      expose Root25;
      expose Root26;
      expose Root27;
      expose Root28;
      expose Root29;
      expose Root30;
      expose Root31;
      expose Root32;
    }
  view roots33 : StandardViewDefinitions::ActionFlowView {
      expose Root1;
      expose Root2;
      expose Root3;
      expose Root4;
      expose Root5;
      expose Root6;
      expose Root7;
      expose Root8;
      expose Root9;
      expose Root10;
      expose Root11;
      expose Root12;
      expose Root13;
      expose Root14;
      expose Root15;
      expose Root16;
      expose Root17;
      expose Root18;
      expose Root19;
      expose Root20;
      expose Root21;
      expose Root22;
      expose Root23;
      expose Root24;
      expose Root25;
      expose Root26;
      expose Root27;
      expose Root28;
      expose Root29;
      expose Root30;
      expose Root31;
      expose Root32;
      expose Root33;
    }
}
