package MultiGeneralView {
  item def Start; item def Request; item def Response;
  part def Root1 { part producer { port link; } part consumer { port link; } connect producer.link to consumer.link; }
  part def Root2 { part producer { port link; } part consumer { port link; } connect producer.link to consumer.link; }
  part def Root3 { part producer { port link; } part consumer { port link; } connect producer.link to consumer.link; }
  part def Root4 { part producer { port link; } part consumer { port link; } connect producer.link to consumer.link; }
  part def Root5 { part producer { port link; } part consumer { port link; } connect producer.link to consumer.link; }
  part def Root6 { part producer { port link; } part consumer { port link; } connect producer.link to consumer.link; }
  part def Root7 { part producer { port link; } part consumer { port link; } connect producer.link to consumer.link; }
  part def Root8 { part producer { port link; } part consumer { port link; } connect producer.link to consumer.link; }
  part def Root9 { part producer { port link; } part consumer { port link; } connect producer.link to consumer.link; }
  part def Root10 { part producer { port link; } part consumer { port link; } connect producer.link to consumer.link; }
  part def Root11 { part producer { port link; } part consumer { port link; } connect producer.link to consumer.link; }
  part def Root12 { part producer { port link; } part consumer { port link; } connect producer.link to consumer.link; }
  part def Root13 { part producer { port link; } part consumer { port link; } connect producer.link to consumer.link; }
  part def Root14 { part producer { port link; } part consumer { port link; } connect producer.link to consumer.link; }
  part def Root15 { part producer { port link; } part consumer { port link; } connect producer.link to consumer.link; }
  part def Root16 { part producer { port link; } part consumer { port link; } connect producer.link to consumer.link; }
  part def Root17 { part producer { port link; } part consumer { port link; } connect producer.link to consumer.link; }
  part def Root18 { part producer { port link; } part consumer { port link; } connect producer.link to consumer.link; }
  part def Root19 { part producer { port link; } part consumer { port link; } connect producer.link to consumer.link; }
  part def Root20 { part producer { port link; } part consumer { port link; } connect producer.link to consumer.link; }
  part def Root21 { part producer { port link; } part consumer { port link; } connect producer.link to consumer.link; }
  part def Root22 { part producer { port link; } part consumer { port link; } connect producer.link to consumer.link; }
  part def Root23 { part producer { port link; } part consumer { port link; } connect producer.link to consumer.link; }
  part def Root24 { part producer { port link; } part consumer { port link; } connect producer.link to consumer.link; }
  part def Root25 { part producer { port link; } part consumer { port link; } connect producer.link to consumer.link; }
  part def Root26 { part producer { port link; } part consumer { port link; } connect producer.link to consumer.link; }
  part def Root27 { part producer { port link; } part consumer { port link; } connect producer.link to consumer.link; }
  part def Root28 { part producer { port link; } part consumer { port link; } connect producer.link to consumer.link; }
  part def Root29 { part producer { port link; } part consumer { port link; } connect producer.link to consumer.link; }
  part def Root30 { part producer { port link; } part consumer { port link; } connect producer.link to consumer.link; }
  part def Root31 { part producer { port link; } part consumer { port link; } connect producer.link to consumer.link; }
  part def Root32 { part producer { port link; } part consumer { port link; } connect producer.link to consumer.link; }
  part def Root33 { part producer { port link; } part consumer { port link; } connect producer.link to consumer.link; }
  view roots1 : StandardViewDefinitions::GeneralView {
      expose Root1;
    }
  view roots2 : StandardViewDefinitions::GeneralView {
      expose Root1;
      expose Root2;
    }
  view roots3 : StandardViewDefinitions::GeneralView {
      expose Root1;
      expose Root2;
      expose Root3;
    }
  view roots8 : StandardViewDefinitions::GeneralView {
      expose Root1;
      expose Root2;
      expose Root3;
      expose Root4;
      expose Root5;
      expose Root6;
      expose Root7;
      expose Root8;
    }
  view roots9 : StandardViewDefinitions::GeneralView {
      expose Root1;
      expose Root2;
      expose Root3;
      expose Root4;
      expose Root5;
      expose Root6;
      expose Root7;
      expose Root8;
      expose Root9;
    }
  view roots16 : StandardViewDefinitions::GeneralView {
      expose Root1;
      expose Root2;
      expose Root3;
      expose Root4;
      expose Root5;
      expose Root6;
      expose Root7;
      expose Root8;
      expose Root9;
      expose Root10;
      expose Root11;
      expose Root12;
      expose Root13;
      expose Root14;
      expose Root15;
      expose Root16;
    }
  view roots17 : StandardViewDefinitions::GeneralView {
      expose Root1;
      expose Root2;
      expose Root3;
      expose Root4;
      expose Root5;
      expose Root6;
      expose Root7;
      expose Root8;
      expose Root9;
      expose Root10;
      expose Root11;
      expose Root12;
      expose Root13;
      expose Root14;
      expose Root15;
      expose Root16;
      expose Root17;
    }
  view roots32 : StandardViewDefinitions::GeneralView {
      expose Root1;
      expose Root2;
      expose Root3;
      expose Root4;
      expose Root5;
      expose Root6;
      expose Root7;
      expose Root8;
      expose Root9;
      expose Root10;
      expose Root11;
      expose Root12;
      expose Root13;
      expose Root14;
      expose Root15;
      expose Root16;
      expose Root17;
      expose Root18;
      expose Root19;
      expose Root20;
      expose Root21;
      expose Root22;
      expose Root23;
      expose Root24;
      expose Root25;
      expose Root26;
      expose Root27;
      expose Root28;
      expose Root29;
      expose Root30;
      expose Root31;
      expose Root32;
    }
  view roots33 : StandardViewDefinitions::GeneralView {
      expose Root1;
      expose Root2;
      expose Root3;
      expose Root4;
      expose Root5;
      expose Root6;
      expose Root7;
      expose Root8;
      expose Root9;
      expose Root10;
      expose Root11;
      expose Root12;
      expose Root13;
      expose Root14;
      expose Root15;
      expose Root16;
      expose Root17;
      expose Root18;
      expose Root19;
      expose Root20;
      expose Root21;
      expose Root22;
      expose Root23;
      expose Root24;
      expose Root25;
      expose Root26;
      expose Root27;
      expose Root28;
      expose Root29;
      expose Root30;
      expose Root31;
      expose Root32;
      expose Root33;
    }
}
