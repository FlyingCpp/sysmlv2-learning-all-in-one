package MultiSequenceView {
  item def Start; item def Request; item def Response;
  part def Root1 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root2 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root3 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root4 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root5 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root6 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root7 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root8 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root9 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root10 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root11 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root12 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root13 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root14 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root15 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root16 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root17 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root18 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root19 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root20 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root21 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root22 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root23 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root24 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root25 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root26 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root27 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root28 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root29 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root30 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root31 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root32 {
    part client[1] { event occurrence requestSource; then event occurrence responseTarget; }
    part server[1] { event occurrence requestTarget; then event occurrence responseSource; }
    message request of Request[1] from client.requestSource to server.requestTarget;
    message response of Response[1] from server.responseSource to client.responseTarget;
  }
  part def Root33 {
    part client[1] { event occurrence requestSource; then event occurrence responseTarget; }
    part server[1] { event occurrence requestTarget; then event occurrence responseSource; }
    message request of Request[1] from client.requestSource to server.requestTarget;
    message response of Response[1] from server.responseSource to client.responseTarget;
  }
  view roots1 : StandardViewDefinitions::SequenceView {
      expose Root1;
    }
  view roots2 : StandardViewDefinitions::SequenceView {
      expose Root1;
      expose Root2;
    }
  view roots3 : StandardViewDefinitions::SequenceView {
      expose Root1;
      expose Root2;
      expose Root3;
    }
  view roots8 : StandardViewDefinitions::SequenceView {
      expose Root1;
      expose Root2;
      expose Root3;
      expose Root4;
      expose Root5;
      expose Root6;
      expose Root7;
      expose Root8;
    }
  view roots9 : StandardViewDefinitions::SequenceView {
      expose Root1;
      expose Root2;
      expose Root3;
      expose Root4;
      expose Root5;
      expose Root6;
      expose Root7;
      expose Root8;
      expose Root9;
    }
  view roots16 : StandardViewDefinitions::SequenceView {
      expose Root1;
      expose Root2;
      expose Root3;
      expose Root4;
      expose Root5;
      expose Root6;
      expose Root7;
      expose Root8;
      expose Root9;
      expose Root10;
      expose Root11;
      expose Root12;
      expose Root13;
      expose Root14;
      expose Root15;
      expose Root16;
    }
  view roots17 : StandardViewDefinitions::SequenceView {
      expose Root1;
      expose Root2;
      expose Root3;
      expose Root4;
      expose Root5;
      expose Root6;
      expose Root7;
      expose Root8;
      expose Root9;
      expose Root10;
      expose Root11;
      expose Root12;
      expose Root13;
      expose Root14;
      expose Root15;
      expose Root16;
      expose Root17;
    }
  view roots32 : StandardViewDefinitions::SequenceView {
      expose Root1;
      expose Root2;
      expose Root3;
      expose Root4;
      expose Root5;
      expose Root6;
      expose Root7;
      expose Root8;
      expose Root9;
      expose Root10;
      expose Root11;
      expose Root12;
      expose Root13;
      expose Root14;
      expose Root15;
      expose Root16;
      expose Root17;
      expose Root18;
      expose Root19;
      expose Root20;
      expose Root21;
      expose Root22;
      expose Root23;
      expose Root24;
      expose Root25;
      expose Root26;
      expose Root27;
      expose Root28;
      expose Root29;
      expose Root30;
      expose Root31;
      expose Root32;
    }
  view roots33 : StandardViewDefinitions::SequenceView {
      expose Root1;
      expose Root2;
      expose Root3;
      expose Root4;
      expose Root5;
      expose Root6;
      expose Root7;
      expose Root8;
      expose Root9;
      expose Root10;
      expose Root11;
      expose Root12;
      expose Root13;
      expose Root14;
      expose Root15;
      expose Root16;
      expose Root17;
      expose Root18;
      expose Root19;
      expose Root20;
      expose Root21;
      expose Root22;
      expose Root23;
      expose Root24;
      expose Root25;
      expose Root26;
      expose Root27;
      expose Root28;
      expose Root29;
      expose Root30;
      expose Root31;
      expose Root32;
      expose Root33;
    }
}
