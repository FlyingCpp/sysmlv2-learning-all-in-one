package MultiStateTransitionView {
  item def Start; item def Request; item def Response;
  state def Root1 { state idle; transition first idle accept Start then active; state active; }
  state def Root2 { state idle; transition first idle accept Start then active; state active; }
  state def Root3 { state idle; transition first idle accept Start then active; state active; }
  state def Root4 { state idle; transition first idle accept Start then active; state active; }
  state def Root5 { state idle; transition first idle accept Start then active; state active; }
  state def Root6 { state idle; transition first idle accept Start then active; state active; }
  state def Root7 { state idle; transition first idle accept Start then active; state active; }
  state def Root8 { state idle; transition first idle accept Start then active; state active; }
  state def Root9 { state idle; transition first idle accept Start then active; state active; }
  state def Root10 { state idle; transition first idle accept Start then active; state active; }
  state def Root11 { state idle; transition first idle accept Start then active; state active; }
  state def Root12 { state idle; transition first idle accept Start then active; state active; }
  state def Root13 { state idle; transition first idle accept Start then active; state active; }
  state def Root14 { state idle; transition first idle accept Start then active; state active; }
  state def Root15 { state idle; transition first idle accept Start then active; state active; }
  state def Root16 { state idle; transition first idle accept Start then active; state active; }
  state def Root17 { state idle; transition first idle accept Start then active; state active; }
  state def Root18 { state idle; transition first idle accept Start then active; state active; }
  state def Root19 { state idle; transition first idle accept Start then active; state active; }
  state def Root20 { state idle; transition first idle accept Start then active; state active; }
  state def Root21 { state idle; transition first idle accept Start then active; state active; }
  state def Root22 { state idle; transition first idle accept Start then active; state active; }
  state def Root23 { state idle; transition first idle accept Start then active; state active; }
  state def Root24 { state idle; transition first idle accept Start then active; state active; }
  state def Root25 { state idle; transition first idle accept Start then active; state active; }
  state def Root26 { state idle; transition first idle accept Start then active; state active; }
  state def Root27 { state idle; transition first idle accept Start then active; state active; }
  state def Root28 { state idle; transition first idle accept Start then active; state active; }
  state def Root29 { state idle; transition first idle accept Start then active; state active; }
  state def Root30 { state idle; transition first idle accept Start then active; state active; }
  state def Root31 { state idle; transition first idle accept Start then active; state active; }
  state def Root32 { state idle; transition first idle accept Start then active; state active; }
  state def Root33 { state idle; transition first idle accept Start then active; state active; }
  view roots1 : StandardViewDefinitions::StateTransitionView {
      expose Root1;
    }
  view roots2 : StandardViewDefinitions::StateTransitionView {
      expose Root1;
      expose Root2;
    }
  view roots3 : StandardViewDefinitions::StateTransitionView {
      expose Root1;
      expose Root2;
      expose Root3;
    }
  view roots8 : StandardViewDefinitions::StateTransitionView {
      expose Root1;
      expose Root2;
      expose Root3;
      expose Root4;
      expose Root5;
      expose Root6;
      expose Root7;
      expose Root8;
    }
  view roots9 : StandardViewDefinitions::StateTransitionView {
      expose Root1;
      expose Root2;
      expose Root3;
      expose Root4;
      expose Root5;
      expose Root6;
      expose Root7;
      expose Root8;
      expose Root9;
    }
  view roots16 : StandardViewDefinitions::StateTransitionView {
      expose Root1;
      expose Root2;
      expose Root3;
      expose Root4;
      expose Root5;
      expose Root6;
      expose Root7;
      expose Root8;
      expose Root9;
      expose Root10;
      expose Root11;
      expose Root12;
      expose Root13;
      expose Root14;
      expose Root15;
      expose Root16;
    }
  view roots17 : StandardViewDefinitions::StateTransitionView {
      expose Root1;
      expose Root2;
      expose Root3;
      expose Root4;
      expose Root5;
      expose Root6;
      expose Root7;
      expose Root8;
      expose Root9;
      expose Root10;
      expose Root11;
      expose Root12;
      expose Root13;
      expose Root14;
      expose Root15;
      expose Root16;
      expose Root17;
    }
  view roots32 : StandardViewDefinitions::StateTransitionView {
      expose Root1;
      expose Root2;
      expose Root3;
      expose Root4;
      expose Root5;
      expose Root6;
      expose Root7;
      expose Root8;
      expose Root9;
      expose Root10;
      expose Root11;
      expose Root12;
      expose Root13;
      expose Root14;
      expose Root15;
      expose Root16;
      expose Root17;
      expose Root18;
      expose Root19;
      expose Root20;
      expose Root21;
      expose Root22;
      expose Root23;
      expose Root24;
      expose Root25;
      expose Root26;
      expose Root27;
      expose Root28;
      expose Root29;
      expose Root30;
      expose Root31;
      expose Root32;
    }
  view roots33 : StandardViewDefinitions::StateTransitionView {
      expose Root1;
      expose Root2;
      expose Root3;
      expose Root4;
      expose Root5;
      expose Root6;
      expose Root7;
      expose Root8;
      expose Root9;
      expose Root10;
      expose Root11;
      expose Root12;
      expose Root13;
      expose Root14;
      expose Root15;
      expose Root16;
      expose Root17;
      expose Root18;
      expose Root19;
      expose Root20;
      expose Root21;
      expose Root22;
      expose Root23;
      expose Root24;
      expose Root25;
      expose Root26;
      expose Root27;
      expose Root28;
      expose Root29;
      expose Root30;
      expose Root31;
      expose Root32;
      expose Root33;
    }
}
